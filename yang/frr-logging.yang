// SPDX-License-Identifier: BSD-2-Clause
module frr-logging {
  yang-version 1.1;
  namespace "http://frrouting.org/yang/frr-logging";
  prefix frr-logging;

  import ietf-syslog-types {
    prefix syslogtypes;
  }

  organization
    "FRRouting";
  contact
    "FRR Users List:       <mailto:frog@lists.frrouting.org>
     FRR Development List: <mailto:dev@lists.frrouting.org>";
  description
    "This module defines logging configuration for FRR.

     Copyright 2025 LabN Consulting L.L.C

     Redistribution and use in source and binary forms, with or without
     modification, are permitted provided that the following conditions
     are met:

     1. Redistributions of source code must retain the above copyright notice,
     this list of conditions and the following disclaimer.

     2. Redistributions in binary form must reproduce the above copyright
     notice, this list of conditions and the following disclaimer in the
     documentation and/or other materials provided with the distribution.

     THIS SOFTWARE IS PROVIDED BY THE COPYRIGHT HOLDERS AND CONTRIBUTORS
     \"AS IS\" AND ANY EXPRESS OR IMPLIED WARRANTIES, INCLUDING, BUT NOT
     LIMITED TO, THE IMPLIED WARRANTIES OF MERCHANTABILITY AND FITNESS FOR
     A PARTICULAR PURPOSE ARE DISCLAIMED. IN NO EVENT SHALL THE COPYRIGHT
     HOLDER OR CONTRIBUTORS BE LIABLE FOR ANY DIRECT, INDIRECT, INCIDENTAL,
     SPECIAL, EXEMPLARY, OR CONSEQUENTIAL DAMAGES (INCLUDING, BUT NOT
     LIMITED TO, PROCUREMENT OF SUBSTITUTE GOODS OR SERVICES; LOSS OF USE,
     DATA, OR PROFITS; OR BUSINESS INTERRUPTION) HOWEVER CAUSED AND ON ANY
     THEORY OF LIABILITY, WHETHER IN CONTRACT, STRICT LIABILITY, OR TORT
     (INCLUDING NEGLIGENCE OR OTHERWISE) ARISING IN ANY WAY OUT OF THE USE
     OF THIS SOFTWARE, EVEN IF ADVISED OF THE POSSIBILITY OF SUCH DAMAGE.";

  revision 2025-06-07 {
    description "Initial revision.";
    reference "FRRouting";
  }

  typedef syslog-format {
    type enumeration {
      enum rfc5424 {
        description "RFC5424 syslog format.";
      }
      enum rfc3164 {
        description "RFC3164 syslog format.";
      }
      enum local-syslogd {
        description "Local syslogd format without hostname.";
      }
      enum journald {
        description "systemd journald native format.";
      }
    }
    description "Log message formatting.";
  }

  container logging {
    description "Logging configuration.";

    container stdout {
      presence "Enable stdout logging";
      description "Logging to stdout.";
      leaf level {
        type syslogtypes:severity;
        default debug;
        description "Lowest level for which to log to stdout.";
      }
    }

    container syslog {
      presence "Enable syslog logging";
      description "Logging to syslog.";
      leaf level {
        type syslogtypes:severity;
        default debug;
        description "Lowest level for which to log to syslog.";
      }
    }

    container file {
      description "Logging to a file.";
      leaf filename {
        type string;
        description "Log filename.";
      }
      leaf level {
        type syslogtypes:severity;
        default debug;
        description "Lowest level for which to log to the file.";
      }
    }

    container filtered-file {
      description
        "Log messages to a file, filtering out messages that match any of the
         filter-text entries.";
      leaf filename {
        type string;
        description "Log filename.";
      }
      leaf level {
        type syslogtypes:severity;
        default debug;
        description "Lowest level for which to log to the filtered file.";
      }
    }

    leaf-list filter-text {
      type string;
      description "Log message filters.";
    }

    list daemon-file {
      key daemon;
      description "Per-daemon log files.";
      leaf daemon {
        type string;
        description "Name of the daemon.";
      }
      leaf filename {
        type string;
        mandatory true;
        description "Log filename.";
      }
      leaf level {
        type syslogtypes:severity;
        default debug;
        description "Lowest level for which to log to the daemon log file.";
      }
    }

    leaf facility {
      type identityref {
        base syslogtypes:syslog-facility;
      }
      default syslogtypes:daemon;
      description "Syslog facility.";
    }

    leaf record-priority {
      type boolean;
      default false;
      description "Include priority in non-syslog messages.";
    }

    leaf timestamp-precision {
      type uint8 {
        range 0..6;
      }
      default 0;
      description "Timestamp precision for log messages.";
    }

    leaf error-category {
      type boolean;
      default true;
      description "Prefix log messages with error category.";
    }

    leaf unique-id {
      type boolean;
      default true;
      description "Prefix log messages with unique identifier.";
    }

    leaf immediate-mode {
      type boolean;
      default false;
      description "Use unbuffered log output.";
    }

    list uid-backtrace {
      key uid;
      description "Log message IDs with backtraces enabled.";
      leaf uid {
        type string;
        description "Unique log message identifier.";
      }
    }

    list extended-syslog {
      key name;
      description "Extended RFC5424 syslog targets.";

      leaf name {
        type string;
        description "Target name.";
      }

      container destination {
        description "Log destination.";
        choice type {
          mandatory true;
          description "Destination type.";

          case file {
            container file {
              presence "Enable file destination";
              description "Log to a file";
              leaf path {
                type string;
                mandatory true;
                description "File path.";
              }
              leaf user {
                type string;
                description "File owner when creating.";
              }
              leaf group {
                type string;
                description "File group when creating.";
              }
              leaf mode {
                type string;
                description "File permissions (octal).";
              }
              leaf no-create {
                type boolean;
                default false;
                description "Do not create file if missing.";
              }
              leaf format {
                type syslog-format;
                default rfc5424;
                description "Log message format.";
              }
            }
          }

          case fifo {
            container fifo {
              presence "Enable FIFO destination";
              description "Log to a FIFO";

              leaf path {
                type string;
                mandatory true;
                description "FIFO path.";
              }
              leaf user {
                type string;
                description "File owner when creating.";
              }
              leaf group {
                type string;
                description "File group when creating.";
              }
              leaf mode {
                type string;
                description "File permissions (octal).";
              }
              leaf no-create {
                type boolean;
                default false;
                description "Do not create file if missing.";
              }
              leaf format {
                type syslog-format;
                default rfc5424;
                description "Log message format.";
              }
            }
          }

          case unix {
            container unix {
              presence "Enable unix socket destination";
              description "Log to a unix socket";

              leaf path {
                type string;
                mandatory true;
                description "Unix socket path.";
              }
              leaf format {
                type syslog-format;
                default rfc5424;
                description "Log message format.";
              }
            }
          }

          case journald {
            container journald {
              presence "Enable journald destination";
              description "Log to systemd journald";
            }
          }

          case syslog {
            container syslog {
              presence "Enable syslog destination";
              description "Log to syslog";

              leaf supports-rfc5424 {
                type boolean;
                default false;
                description "Use RFC5424 format.";
              }
            }
          }

          case fd {
            container fd {
              presence "Enable file descriptor destination";
              description "Log to a file descriptor";

              choice source {
                mandatory true;
                description "File descriptor source.";

                case number {
                  leaf number {
                    type uint8 {
                      range 0..63;
                    }
                    description "File descriptor number.";
                  }
                }
                case envvar {
                  leaf envvar {
                    type string;
                    description "Environment variable with descriptor.";
                  }
                }
                case stdout {
                  leaf stdout {
                    type empty;
                    description "Use standard output.";
                  }
                }
                case stderr {
                  leaf stderr {
                    type empty;
                    description "Use standard error.";
                  }
                }
              }
              leaf format {
                type syslog-format;
                default rfc5424;
                description "Log message format.";
              }
            }
          }

          case none {
            container none {
              presence "Disable destination";
              description "Disable logging to this target.";
            }
          }
        }
      }

      leaf level {
        type syslogtypes:severity;
        default debug;
        description "Lowest level for which to log to the target.";
      }

      leaf facility {
        type identityref {
          base syslogtypes:syslog-facility;
        }
        default syslogtypes:daemon;
        description "Syslog facility.";
      }

      // container struct-data {
        leaf code-location {
          type boolean;
          default true;
          description "Include source code location.";
        }

        leaf version {
          type boolean;
          default false;
          description "Include FRR version.";
        }

        leaf error-category {
          type boolean;
          default true;
          description "Include error category.";
        }

        leaf unique-id {
          type boolean;
          default true;
          description "Include unique message identifier.";
        }
      // }

      leaf format-args {
        type boolean;
        default false;
        description "Include individual format arguments.";
      }

      leaf timestamp-precision {
        type uint8 {
          range 0..9;
        }
        default 6;
        description "Subsecond timestamp precision.";
      }

      leaf timestamp-local-time {
        type boolean;
        default false;
        description "Use local time zone for timestamps.";
      }
    }
  }
}
